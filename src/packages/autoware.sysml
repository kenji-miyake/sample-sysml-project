package AutonomousVehicle
{
}

item VectorMap;
item PointCloudMap;

port def P_VectorMap {
    in item vector_map : VectorMap
}


package AutowareComponent
{
	part def Map {
    }

	part def Sensing {

    }

	part def Localization {

    }

	part def Perception {

    }

	part def Planning {

    }

	part def Control {

    }

	part def Vehicle {

    }

	part def System {

    }
}
